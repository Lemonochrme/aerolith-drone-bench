import FreeCAD as App, Part, math, json
from pathlib import Path
V=App.Vector
T=float(globals().get("THICKNESS",4.0)); TOOL=3.0
CLEAR=float(globals().get("SLOT_CLEARANCE",.05))
LASER=globals().get("LASER",False)
OUT=Path(__file__).resolve().parent
src=json.loads((OUT/'sources/contours.json').read_text(encoding='utf-8'))
def rot(p,a):
 a=math.radians(a);return V(p.x*math.cos(a)-p.y*math.sin(a),p.x*math.sin(a)+p.y*math.cos(a),p.z)
def rounded(points,r=4,variable=False,radii=None,cap_ratio=.45):
 ps=[V(x,y,0) for x,y in points];corners=[]
 # Counterclockwise winding is not necessary: signed turn defines arc normal.
 for i,p in enumerate(ps):
  prev,nxt=ps[i-1],ps[(i+1)%len(ps)];u=p-prev;u.normalize();v=nxt-p;v.normalize()
  angle=math.atan2(u.cross(v).z,u.dot(v))
  if abs(angle)<1e-7:corners.append((p,p,None));continue
  radius=radii[i] if radii is not None else (1.6 if angle<0 else 1.0) if variable else r
  if radius<1e-8:corners.append((p,p,None));continue
  trim=radius*math.tan(abs(angle)/2)
  cap=min((p-prev).Length,(nxt-p).Length)*cap_ratio
  if trim>cap:
   radius=cap/math.tan(abs(angle)/2);trim=cap
  a=p-u*trim;b=p+v*trim;sgn=1 if angle>0 else -1
  c=a+V(-u.y,u.x,0)*radius*sgn
  middle=c+rot(a-c,math.degrees(angle)/2)
  corners.append((a,b,(middle,radius,angle)))
 es=[]
 for i,(a,b,data) in enumerate(corners):
  last=corners[i-1][1]
  if (a-last).Length>1e-7:es.append(Part.makeLine(last,a))
  if data:es.append(Part.Arc(a,data[0],b).toShape())
 return Part.Wire(es)
def capsule(cx,cy,length,width,angle=0):
 radius=width/2;h=length/2-radius
 ps=[V(-h,-radius),V(h,-radius),V(h,radius),V(-h,radius)]
 es=[Part.makeLine(ps[0],ps[1]),Part.Arc(ps[1],V(h+radius,0),ps[2]).toShape(),Part.makeLine(ps[2],ps[3]),Part.Arc(ps[3],V(-h-radius,0),ps[0]).toShape()]
 w=Part.Wire(es);w.rotate(V(),V(0,0,1),angle);w.translate(V(cx,cy));return w
MORTISES={}
def mortise(cx,cy,length,width,angle=0):
 if LASER:
  w=Part.makePolygon([V(-length/2,-width/2),V(length/2,-width/2),V(length/2,width/2),V(-length/2,width/2),V(-length/2,-width/2)])
  w.rotate(V(),V(0,0,1),angle);w.translate(V(cx,cy));return Part.Wire(w.Edges)
 key=(length,width)
 if key not in MORTISES:
  r=min(TOOL/2+.1,width/2)
  assert r>=TOOL/2-1e-9, 'Mortaise plus etroite que la fraise'
  f=Part.Face(rounded([(-length/2,-width/2),(length/2,-width/2),(length/2,width/2),(-length/2,width/2)],r,cap_ratio=.5)).extrude(V(0,0,1))
  for sx in [-1,1]:
   for sy in [-1,1]:
    # T-bone: move the cutter perpendicular to the long edge, not diagonally.
    a=V(sx*(length/2-r),sy*(width/2-r));b=V(sx*(length/2-r),sy*width/2)
    delta=b-a;mid=(a+b)*.5
    sweep=Part.Face(capsule(mid.x,mid.y,delta.Length+2*r,2*r,math.degrees(math.atan2(delta.y,delta.x)))).extrude(V(0,0,1))
    f=f.fuse(sweep).removeSplitter()
  bottom=[q for q in f.Faces if q.BoundBox.ZLength<1e-6 and abs(q.CenterOfMass.z)<1e-6]
  assert len(bottom)==1
  MORTISES[key]=bottom[0].OuterWire
  box=MORTISES[key].BoundBox
  assert abs(box.XLength-length)<1e-7 and abs(box.YLength-width-2*r)<1e-7
 w=MORTISES[key].copy();w.rotate(V(),V(0,0,1),angle);w.translate(V(cx,cy));return w

def circle(x,y,r):return Part.Wire([Part.makeCircle(r,V(x,y))])
def face(outer,holes):return Part.makeFace([outer]+holes,'Part::FaceMakerBullseye')
def sourceface(prefix):
 es=next(v for k,v in src.items() if k.startswith(prefix));edges=[]
 for e in es:
  if e[0]=='LINE':edges.append(Part.makeLine(V(*e[1]),V(*e[2])))
  elif e[0]=='CIRCLE':edges.append(Part.makeCircle(e[2],V(*e[1])))
  else:edges.append(Part.makeCircle(e[2],V(*e[1]),V(0,0,1),e[3],e[4] if e[4]>e[3] else e[4]+360))
 for e in edges:e.fixTolerance(.001)
 return Part.makeFace([Part.Wire(w) for w in Part.sortEdges(edges,.01)],'Part::FaceMakerBullseye')
# Main plate: remove logos, microcuts and the unused M2 electronics pattern.
basepoints=[(-20,-125),(20,-125),(29,-112),(27,-98),(43,-62),(52,-25),(60,-6),(60,6),(52,25),(43,62),(27,98),(29,112),(20,125),(-20,125),(-29,112),(-27,98),(-43,62),(-52,25),(-60,6),(-60,-6),(-52,-25),(-43,-62),(-27,-98),(-29,-112)]
rootfeet=[]
for x,y,a in [(14.180925185,102.561125984,22.198102),(41.414460411,11.777008489,47.198102)]:
 for sx in [-1,1]:
  for sy in [-1,1]:
   for side in [-1,1]:
    v=rot(V(4.5,side*8.5),a);rootfeet.append((sx*(x+v.x),sy*(y+v.y)))
# Keep only used electronics and structural mounting patterns.
baseholes=[circle(x,y,1.65) for x in [-15.25,15.25] for y in [-15.25,15.25]]
baseholes += [circle(x,y,2.25) for x in [-25,25] for y in [-25,25]]
for x,y in rootfeet:baseholes.append(circle(x,y,1.65))
roots=[(14.180925185,102.561125984,22.198102),(41.414460411,11.777008489,47.198102)]
for x,y,a in roots:
 for sx in [-1,1]:
  for sy in [-1,1]:baseholes.append(mortise(sx*x,sy*y,14.08,T+CLEAR,math.degrees(math.atan2(sy*math.sin(math.radians(a)),sx*math.cos(math.radians(a))))))
for x in [-25,25]:
 for y in [-45,45]:baseholes.append(capsule(x,y,27,5,90))
# Shared central windows and outer windows accept two ESC straps per row.
for y in [-70,70]:
 for x in [-29,0,29]:baseholes.append(capsule(x,y,8,4,90))
base=face(rounded(basepoints,12),baseholes)
# Keep tenon lands and assembly centerlines; soften nonfunctional corners.
def arm(long=False):
 shift=15 if long else 0;root=-67.5-shift;ends=[48.5+shift,68.5+shift];xmin=-80-shift;xmax=80+shift
 low=[(xmin,-10),(root-7,-10),(root-7,-10-T),(root+7,-10-T),(root+7,-10),(-48-shift,-10),(-43-shift,-13.5),(9+shift,-9),(18+shift,-8),(ends[0]-6,-8),(ends[0]-6,-8-T),(ends[0]+6,-8-T),(ends[0]+6,-8),(ends[1]-6,-8),(ends[1]-6,-8-T),(ends[1]+6,-8-T),(ends[1]+6,-8),(xmax,-8)]
 ps=low+[(x,-y) for x,y in reversed(low)]
 # Four integral landing feet, one on each short arm; leave the upper edge intact.
 if not long:
  i=low.index((9,-9))
  low=low[:i]+[(-31,-12.5),(-21,-17),(-10,-45),(10,-45),(15,-16),(18,-8)]+low[i+2:]
  ps=low+ps[len(ps)//2:]
 # Blend the free span without cutting semicircular notches into its edges.
 # Cutter reliefs belong only to the functional tenon shoulders.
 radii=[];reliefs=[]
 for i,(x,y) in enumerate(ps):
  u=V(x,y)-V(*ps[i-1]);v=V(*ps[(i+1)%len(ps)])-V(x,y)
  concave=u.cross(v).z<-1e-7
  tenon=any(abs(x-c)<7.01 for c in [root]+ends)
  foot_corner=not long and y < -14 and -32 <= x <= 16
  radii.append((0 if tenon else 8.0) if concave else (4.0 if foot_corner else 1.0))
  if concave and tenon:reliefs.append((x,y))
 f=Part.Face(rounded(ps,radii=radii))
 for x,y in ([] if LASER else reliefs):
  # T-bone at the shoulder, offset away from the tenon to preserve its width.
  c=min([root]+ends,key=lambda c:abs(x-c));side=1 if x>c else -1
  r=TOOL/2+.1;cy=y+(r/2 if y>0 else -r/2)
  f=f.cut(Part.Face(capsule(x+side*r,cy,3*r,2*r,90)))
 return Part.Face(f.removeSplitter().Faces[0].OuterWire)
short=arm();long=arm(True)
# Motor support: smooth outline, retain mounting centers and shaft clearance.
MC=V(2.563971143,-2.313539946)
MOTOR_CENTER=MC+V(0,-7)
MOTOR_DIAGONAL=19.0
MOTOR_HALF_SIDE=MOTOR_DIAGONAL/(2*math.sqrt(2))
mpoints=[(MOTOR_CENTER.x+x,MOTOR_CENTER.y+y) for x,y in [(-16,-30.5),(16,-30.5),(26.5,-19),(28,-5),(28,5),(26.5,19),(16,30.5),(-16,30.5),(-26.5,19),(-28,5),(-28,-5),(-26.5,-19)]]
mholes=[circle(MOTOR_CENTER.x,MOTOR_CENTER.y,4.5)]
# GTSkytenRC 3115: user-confirmed 19 mm between opposite holes (PCD 19).
for x in [-MOTOR_HALF_SIDE,MOTOR_HALF_SIDE]:
 for y in [-MOTOR_HALF_SIDE,MOTOR_HALF_SIDE]:mholes.append(circle(MOTOR_CENTER.x+x,MOTOR_CENTER.y+y,1.65))
for x,y,a in [(-14.184693509,-8.329579633,77.198102),(-9.75307754,11.173260666,77.198102),(19.249767711,-8.505751186,102.198102),(15.023919308,11.042706692,102.198102)]:mholes.append(mortise(x,y,12.08,T+CLEAR,a))
# Four closures surround the motor, outside the arm passages.
motorfeet=[(MOTOR_CENTER.x+x,MOTOR_CENTER.y+y) for x,y in [(-21.5,16.5),(21.5,16.5),(-12,-22),(12,-22)]]
for x,y in motorfeet:mholes.append(circle(x,y,1.65))
motor_outer=rounded(mpoints,8)
assert (Part.Face(motor_outer).CenterOfMass-MOTOR_CENTER).Length<1e-6
motor=face(motor_outer,mholes)
assert min(h.distToShape(motor_outer)[0] for h in mholes) > (3.5 if LASER else 3.4)
# Fit coupon: alternative widths for actual sheet and spindle runout.
couponholes=[mortise(-25+i*12,0,14.08,T+[0,.025,.05,.075,.1,.15][i],90) for i in range(6)]
coupon=face(rounded([(-37,-16),(47,-16),(47,16),(-37,16)],4),couponholes)
forms={'01_Platine_centrale':base,'02_Bras_court':short,'03_Bras_long':long,'04_Socle_moteur':motor,'05_Coupon_ajustement':coupon}

# Native FreeCAD project, separated from the calibration bench.
if LASER or abs(T-4.0)>1e-9:
 raise RuntimeError('Le projet complet est celui du carbone 4 mm. Utiliser exporter_laser.py pour le prototype MDF.')
import Import
(OUT/'dxf').mkdir(exist_ok=True);(OUT/'.build').mkdir(exist_ok=True)
D=App.newDocument('Aerolith_Chassis_CNC_R11');D.Label='Aerolith / Châssis CNC R11 / carbone 4 mm / fraise 3 mm'
settings=D.addObject('Spreadsheet::Sheet','Parametres');settings.Label='00 / Références de fabrication ; reconstruction par macro'
for c,val in {'A1':'PARAMÈTRE / référence','B1':'VALEUR','A2':'Épaisseur carbone (mm)','B2':str(T),'A3':'Fraise (mm)','B3':str(TOOL),'A4':'Jeu nominal rainure (mm)','B4':str(CLEAR),'A5':'Rainure (mm)','B5':str(T+CLEAR),'A6':'Entretoises centrales (mm)','B6':'20','A7':'Entretoises moteur (mm)','B7':'16','A10':'FC / entraxe suppose','B10':'30.5 x 30.5','A11':'ESC / enveloppe provisoire','B11':'50 x 18 x 8 mm','A12':'Batterie / enveloppe provisoire','B12':'148 x 44 x 52 mm','A13':'Moteurs','B13':'GTSkytenRC 3115 640KV / dimensions a confirmer','A14':'Helices','B14':'9x5x3 / diametre 228.6 / pas 127','A8':'Note','B8':'Modifier la macro et reconstruire pour changer les interfaces'}.items():settings.set(c,val)
settings.setColumnWidth('A',320);settings.setColumnWidth('B',420);settings.setStyle('A1:B1','bold','add')
lib=D.addObject('App::Part','Bibliotheque');lib.Label='01 / Pièces planes / historique d’extrusion'
assembly=D.addObject('App::Part','Chassis');assembly.Label='02 / Châssis assemblé'
masters={};links=[];shapes=[]
qty={'01_Platine_centrale':2,'02_Bras_court':4,'03_Bras_long':4,'04_Socle_moteur':8,'05_Coupon_ajustement':1}
colors={'01_Platine_centrale':(.13,.18,.23),'02_Bras_court':(.19,.25,.30),'03_Bras_long':(.19,.25,.30),'04_Socle_moteur':(.17,.22,.27),'05_Coupon_ajustement':(.3,.5,.65)}
report={'version':'R11','epaisseur_mm':T,'fraise_mm':TOOL,'jeu_rainure_mm':CLEAR,'gcode_genere':False,'formes':{},'collisions_carbone_mm3':[]}
# Export analytic 2D contours as closed polylines with exact circular arc bulges.
def contour_data(f):
 data=[]
 for w in f.Wires:
  if len(w.Edges)==1 and isinstance(w.Edges[0].Curve,Part.Circle):
   c=w.Edges[0].Curve;data.append({'type':'CIRCLE','center':[c.Center.x,c.Center.y],'radius':c.Radius});continue
  ordered=w.OrderedEdges;nodes=[];current=None;last=None
  for e in ordered:
   a=e.valueAt(e.FirstParameter);b=e.valueAt(e.LastParameter);mid=e.valueAt((e.FirstParameter+e.LastParameter)/2)
   if current is None:
    if e.Orientation=='Reversed':a,b=b,a
   elif (b-current).Length<(a-current).Length:a,b=b,a
   if current is not None:assert (a-current).Length<1e-5
   bulge=0
   if isinstance(e.Curve,Part.Circle):
    c=e.Curve.Center
    ang=lambda p:math.atan2(p.y-c.y,p.x-c.x)
    aa,bb,mm=ang(a),ang(b),ang(mid);sweep=(bb-aa)%(2*math.pi)
    if (mm-aa)%(2*math.pi)>sweep+1e-7:sweep-=2*math.pi
    bulge=math.tan(sweep/4)
   nodes.append([a.x,a.y,bulge]);current=b
  assert (current-V(nodes[0][0],nodes[0][1])).Length<1e-5
  data.append({'type':'LWPOLYLINE','closed':True,'points':nodes})
 return data
contours={}
for name,f in forms.items():
 assert f.isValid() and len(f.Faces)==1
 profile=D.addObject('PartDesign::Feature',name+'_Profil');lib.addObject(profile);profile.Label=name+' / contour CNC';profile.Shape=f
 body=D.addObject('Part::Extrusion',name);lib.addObject(body);body.Base=profile;body.DirMode='Normal';body.LengthFwd=T;body.Solid=True;body.Label=name.replace('_',' ');body.ViewObject.ShapeColor=colors[name]
 for typ,prop in [('App::PropertyInteger','Quantite'),('App::PropertyString','Fabrication')]:body.addProperty(typ,prop,'CNC')
 body.Quantite=qty[name];body.Fabrication='Carbone 4 mm ; fraise Ø3 ; jeu total 0.05 mm ; reliefs locaux de fraise'
 D.recompute();masters[name]=body;profile.Visibility=False;body.Visibility=False
 solid=f.extrude(V(0,0,T));assert solid.isValid() and len(solid.Solids)==1
 hs=[w for w in f.Wires if not w.isSame(f.OuterWire)]
 ds=[w.distToShape(f.OuterWire)[0] for w in hs]+[w.distToShape(v)[0] for i,w in enumerate(hs) for v in hs[i+1:]]
 original=sourceface({'01_Platine_centrale':'Base','02_Bras_court':'Bras court','03_Bras_long':'Bras long','04_Socle_moteur':'Socle'}[name]) if name!='05_Coupon_ajustement' else None
 report['formes'][name]={'quantite':qty[name],'solide_valide':solid.isValid(),'perimetre_usinage_mm':round(sum(e.Length for e in f.Edges),3),'perimetre_origine_mm':round(sum(e.Length for e in original.Edges),3) if original else None,'aire_mm2':round(f.Area,3),'aire_originale_mm2':round(original.Area,3) if original else None,'ligament_min_mm':round(min(ds),3) if ds else None,'nombre_contours':len(f.Wires),'contours_fermes':all(w.isClosed() for w in f.Wires),'encombrement_mm':[round(f.BoundBox.XLength,3),round(f.BoundBox.YLength,3),T]}
 contours[name]=contour_data(f)
def link(name,key,pos=(0,0,0),rotation=None):
 o=D.addObject('App::Link',name);assembly.addObject(o);o.setLink(masters[key]);o.LinkPlacement=App.Placement(V(*pos),rotation or App.Rotation());o.Visibility=True;links.append(o)
 s=forms[key].extrude(V(0,0,T));s.Placement=o.LinkPlacement;shapes.append((name,s));return o
link('Platine_inferieure','01_Platine_centrale',(0,0,-20-T));link('Platine_superieure','01_Platine_centrale')
mr=App.Rotation(V(0,0,1),-55);a=math.radians(22.198102);tab=V(roots[0][0]+116*math.cos(a),roots[0][1]+116*math.sin(a),0);mp=tab-mr.multVec(V(-14.184693509,-8.329579633,0))
for sx in [-1,1]:
 for sy in [-1,1]:
  q=('D' if sx>0 else 'G')+('_AV' if sy>0 else '_AR')
  for label,key,(x,y,a),rx in [('Court','02_Bras_court',roots[0],-67.5),('Long','03_Bras_long',roots[1],-82.5)]:
   angle=math.degrees(math.atan2(sy*math.sin(math.radians(a)),sx*math.cos(math.radians(a))))
   rr=App.Rotation(V(0,0,1),angle).multiply(App.Rotation(V(1,0,0),90));p=V(sx*x,sy*y,-10)-rr.multVec(V(rx,0,T/2))
   link('Bras_'+label+'_'+q,key,tuple(p),rr)
  M=App.Matrix();M.A11=sx;M.A22=sy;M.A33=sx*sy;rr=App.Rotation(M).multiply(mr)
  for z,label in [(-18-T,'Bas'),(-2,'Haut')]:link('Support_moteur_'+label+'_'+q,'04_Socle_moteur',(sx*mp.x,sy*mp.y,z+(T if sx*sy<0 else 0)),rr)
# Mechanical joints and equipment are defined below.
hardware=[];equipment=[]
joints=D.addObject('App::Part','Liaisons');assembly.addObject(joints);joints.Label='Entretoises et visserie de fermeture'
elec=D.addObject('App::Part','Electronique');assembly.addObject(elec);elec.Label='FC 30.5 et 4 ESC provisoires'
propulsion=D.addObject('App::Part','Propulsion');assembly.addObject(propulsion);propulsion.Label='3115 640KV / tripales 9x5x3'
def addpart(name,shape,parent,color,spec,kind='hardware'):
 assert shape.isValid(),name
 o=D.addObject('PartDesign::Feature',name);parent.addObject(o);o.Shape=shape;o.ViewObject.ShapeColor=color
 o.addProperty('App::PropertyString','Specification','Modele');o.Specification=spec
 (hardware if kind=='hardware' else equipment).append(o);return o
metal=(.65,.69,.73);black=(.12,.13,.15);green=(.08,.42,.24)
def positioned(shape,p,rr=None):
 shape=shape.copy();shape.Placement=App.Placement(p,rr or App.Rotation());return shape
def spacer(name,x,y,z,L,rad=3,inner=1.65):
 return addpart(name,Part.makeCylinder(rad,L,V(x,y,z)).cut(Part.makeCylinder(inner,L,V(x,y,z))),joints,metal,f'Entretoise metallique L{L} / passage {2*inner}')
def bolt(name,p,axis,L,nutdist=None):
 ax=V(*axis);ax.normalize();s=Part.makeCylinder(1.5,L,p,ax).fuse(Part.makeCylinder(2.75,3,p-ax*3,ax))
 # Hex nut represented at the far clamped face, not at the thread tip.
 o=addpart(name,s,joints,(.36,.39,.42),f'Vis M3x{L}, geometrie sans filetage')
 dist=nutdist if nutdist is not None else 28 if 'Fermeture_racine' in name else 24 if 'Fermeture_' in name else 8 if 'racine' in name else 6
 vertices=[V(3.175*math.cos(k*math.pi/3),3.175*math.sin(k*math.pi/3),0) for k in range(7)]
 nut=Part.Face(Part.makePolygon(vertices)).extrude(V(0,0,4)).cut(Part.makeCylinder(1.6,4))
 addpart('Ecrou_M3',positioned(nut,p+ax*dist,App.Rotation(V(0,0,1),ax)),joints,metal,'Ecrou frein M3, hauteur indicative 4, filetage non represente')
 return o
for sx in [-1,1]:
 for sy in [-1,1]:
  q=('D' if sx>0 else 'G')+('_AV' if sy>0 else '_AR')
  for label,(x,y,a) in [('Court',roots[0]),('Long',roots[1])]:
   ag=math.degrees(math.atan2(sy*math.sin(math.radians(a)),sx*math.cos(math.radians(a))));center=V(sx*x,sy*y,0);n=rot(V(0,1),ag)
   for side in [-1,1]:
    foot=center+rot(V(4.5,0),ag)+n*(side*8.5);spacer('Entretoise_racine_L20',foot.x,foot.y,-20,20)
    bolt('Fermeture_racine_M3x35',V(foot.x,foot.y,-24),(0,0,1),35)
  for fx,fy in motorfeet:
   foot=mp+mr.multVec(V(fx,fy));spacer('Entretoise_moteur_L16',sx*foot.x,sy*foot.y,-18,16)
   bolt('Fermeture_moteur_M3x30',V(sx*foot.x,sy*foot.y,-22),(0,0,1),30)
for x in [-25,25]:
 for y in [-25,25]:spacer('Entretoise_centrale_M4_L20',x,y,-20,20,4,2.25)
for x in [-25,25]:
 for y in [-25,25]:
  addpart('Vis_centrale_M4x40',Part.makeCylinder(2,40,V(x,y,-24)).fuse(Part.makeCylinder(3.5,4,V(x,y,-28))),joints,black,'M4x40, fermeture des platines')
  vertices=[V(x+4.042*math.cos(k*math.pi/3),y+4.042*math.sin(k*math.pi/3),4) for k in range(7)]
  addpart('Ecrou_central_M4',Part.Face(Part.makePolygon(vertices)).extrude(V(0,0,5)).cut(Part.makeCylinder(2.1,5,V(x,y,4))),joints,metal,'Ecrou frein M4, hauteur indicative 5, filetage non represente')
# FC mounting is independent from the structural spacers.
fcface=face(rounded([(-18,-18),(18,-18),(18,18),(-18,18)],2),[circle(x,y,1.65) for x in [-15.25,15.25] for y in [-15.25,15.25]])
fc=addpart('FC_30_5',positioned(fcface.extrude(V(0,0,1.6)),V(0,0,-13)),elec,green,'Entraxe 30.5x30.5 fourni ; carte 36x36x1.6 et composants indicatifs','equipment')
addpart('FC_composants',Part.makeBox(12,12,2,V(-6,-6,-11.4)).fuse(Part.makeBox(12,6,5,V(-6,9,-11.4))),elec,black,'Implantation indicative, carte exacte non fournie','equipment')
for x in [-15.25,15.25]:
 for y in [-15.25,15.25]:
  addpart('Silentbloc_FC',Part.makeCylinder(3.1,7,V(x,y,-20)).cut(Part.makeCylinder(1.65,7,V(x,y,-20))),elec,(.75,.25,.15),'Support souple indicatif L7','equipment')
for i,(x,y) in enumerate([(-14,-60),(14,-60),(-14,60),(14,60)],1):
 addpart('Isolant_ESC_'+str(i),Part.makeBox(18,50,2,V(x-9,y-25,-20)),elec,(.25,.25,.25),'Adhesif isolant provisoire 2 mm','equipment')
 board=Part.makeBox(18,50,1.6,V(x-9,y-25,-18));addpart('ESC_'+str(i),board,elec,green,'Reference non choisie ; enveloppe 50x18x8 mm, hors cables','equipment')
 chips=[]
 for yy in [-16,-5,6,17]:chips.append(Part.makeBox(13,8,6.4,V(x-6.5,y+yy-4,-16.4)))
 addpart('ESC_'+str(i)+'_composants',Part.makeCompound(chips),elec,black,'Composants indicatifs','equipment')
# Four ESC ties use six slots, sharing the central slot in each row.
for x,y in [(-14,-60),(14,-60),(-14,60),(14,60)]:
 xl=-29 if x<0 else 0;xr=xl+29
 yy=(1 if y>0 else -1)*(68.5 if x<0 else 71.5)
 tie=Part.makeBox(29.8,2.5,.8,V(xl-.4,yy-1.25,-24.8)).fuse(Part.makeBox(29.8,2.5,.8,V(xl-.4,yy-1.25,-10)))
 for xx in [xl,xr]:tie=tie.fuse(Part.makeBox(.8,2.5,15.6,V(xx-.4,yy-1.25,-24.8)))
 addpart('Collier_ESC',tie.removeSplitter(),elec,(.83,.33,.12),'Collier nylon 2.5x100, trajet simplifie ; six passes dans les platines','equipment')
# Battery remains outside the two plates; no electrical specification inferred.
addpart('Batterie_provisoire',Part.makeBox(44,148,52,V(-22,-74,11)),elec,(.18,.32,.53),'Reference non choisie ; enveloppe 148x44x52 mm, aucune capacite ni tension imposee','equipment')
addpart('Pad_batterie',Part.makeBox(40,140,7,V(-20,-70,4)),elec,(.25,.25,.25),'Pad isolant indicatif 7 mm','equipment')
for x in [-15.25,15.25]:
 for y in [-15.25,15.25]:bolt('Fixation_FC_M3x20',V(x,y,-24),(0,0,1),20,12.6)
for y in [-45,45]:
 strap=Part.makeBox(52,20,1,V(-26,y-10,63)).fuse(Part.makeBox(52,20,1,V(-26,y-10,-1)))
 for x in [-26,25]:strap=strap.fuse(Part.makeBox(1,20,65,V(x,y-10,-1)))
 addpart('Sangle_batterie',strap.removeSplitter(),elec,(.77,.37,.1),'Sangle indicative largeur 20 mm, passant dans les lumieres de la platine','equipment')
# Nominal 9x5x3: 228.6 diameter, geometric pitch 127, three blades.
def propeller(hand):
 profiles=[]
 for x,w in [(8.5,5),(15,13),(28,22),(52,24),(80,20),(103,12),(114.3,.7)]:
  ell=Part.Wire([Part.Ellipse(V(),w/2,min(.85,w/3)).toShape()]);ell.rotate(V(),V(0,0,1),90);ell.rotate(V(),V(0,1,0),90)
  pitch=hand*math.degrees(math.atan(127/(2*math.pi*x)));ell.rotate(V(),V(1,0,0),pitch);ell.translate(V(x,0,0));profiles.append(ell)
 blade=Part.makeLoft(profiles,True,False);s=Part.makeCylinder(9,9,V(0,0,-4.5))
 for a in [0,120,240]:
  b=blade.copy();b.rotate(V(),V(0,0,1),a);s=s.fuse(b)
 return s.cut(Part.makeCylinder(2.6,14,V(0,0,-7))).removeSplitter()
props={hand:propeller(hand) for hand in [-1,1]}
for sx in [-1,1]:
 for sy in [-1,1]:
  q=('D' if sx>0 else 'G')+('_AV' if sy>0 else '_AR');cc=mp+mr.multVec(MOTOR_CENTER);x,y=sx*cc.x,sy*cc.y
  # Simplified 3115 envelope. GTSkytenRC manufacturer drawing not available.
  shell=Part.makeCylinder(19,27,V(x,y,5)).cut(Part.makeCylinder(16.8,27,V(x,y,5)))
  cap=Part.makeCylinder(19,3,V(x,y,32))
  for a in range(0,360,60):
   vv=rot(V(11,0),a);cap=cap.cut(Part.makeCylinder(3.5,5,V(x+vv.x,y+vv.y,31)))
  addpart('GTSkytenRC_3115_640KV_'+q,shell.fuse(cap),propulsion,(.22,.23,.25),'Modele simplifie ; diametre 38 / corps 33 / arbre M5, dimensions GTSkytenRC non confirmees','equipment')
  base=Part.makeCylinder(17,3,V(x,y,2))
  for hx in [-MOTOR_HALF_SIDE,MOTOR_HALF_SIDE]:
   for hy in [-MOTOR_HALF_SIDE,MOTOR_HALF_SIDE]:
    vv=mr.multVec(V(hx,hy));base=base.cut(Part.makeCylinder(1.65,5,V(x+sx*vv.x,y+sy*vv.y,1)))
  addpart('Embase_moteur_'+q,base,propulsion,metal,'4 trous M3 : diagonales 19 mm, cote 19/sqrt(2) mm','equipment')
  for hx in [-MOTOR_HALF_SIDE,MOTOR_HALF_SIDE]:
   for hy in [-MOTOR_HALF_SIDE,MOTOR_HALF_SIDE]:
    vv=mr.multVec(V(hx,hy));bx,by=x+sx*vv.x,y+sy*vv.y
    addpart('Fixation_moteur_M3x8',Part.makeCylinder(1.5,8,V(bx,by,-2)).fuse(Part.makeCylinder(2.75,3,V(bx,by,-5))),joints,black,'M3x8 provisoire ; profondeur de vissage moteur a confirmer')
  addpart('Stator_3115_'+q,Part.makeCylinder(15.5,15,V(x,y,8)),propulsion,(.61,.32,.12),'Stator nominal 31x15','equipment')
  addpart('Arbre_M5_'+q,Part.makeCylinder(2.5,49,V(x,y,2)),propulsion,metal,'Arbre M5 simplifie, longueur indicative','equipment')
  pp=props[1 if sx*sy>0 else -1].copy();pp.translate(V(x,y,43.5))
  addpart('Helice_9x5x3_'+q,pp,propulsion,(.47,.49,.52),'Tripale diametre 228.6, pas geometrique 127 ; profil et moyeu indicatifs, pas un modele constructeur','equipment')

D.recompute()
# Detect unintended carbon/ carbon overlap in the assembled chassis.
for i,(n,s) in enumerate(shapes):
 for m,t in shapes[i+1:]:
  if s.BoundBox.intersect(t.BoundBox):
   vol=s.common(t).Volume
   if vol>.001:report['collisions_carbone_mm3'].append([n,m,round(vol,6)])
assert not report['collisions_carbone_mm3'],report['collisions_carbone_mm3']
feet=[s for n,s in shapes if n.startswith('Bras_Court_')]
assert len(feet)==4 and all(abs(s.BoundBox.ZMin+55)<1e-6 for s in feet)
others=[s for n,s in shapes if not n.startswith('Bras_Court_')]+[o.Shape for o in hardware+equipment]
ground_clearance=min(s.BoundBox.ZMin for s in others)+55
assert ground_clearance>20
report['pieds']={'quantite':4,'plan_appui_z_mm':-55,'garde_sous_platine_basse_mm':35-T,
                 'garde_sous_autres_pieces_mm':round(ground_clearance,3)}
report['volume_carbone_chassis_mm3']=round(sum(forms[n].Area*T*q for n,q in qty.items() if 'Coupon' not in n),3)
report['volume_origine_meme_epaisseur_mm3']=round(sum(d['aire_originale_mm2']*T*d['quantite'] for d in report['formes'].values() if d['aire_originale_mm2'] is not None),3)
# Clearances apply to the modeled envelopes, not to unspecified real equipment.
report['interferences_carbone_equipements']=[]
for n,shape in shapes:
 for obj in hardware+equipment:
  other=obj.Shape
  if shape.BoundBox.intersect(other.BoundBox):
   volume=shape.common(other).Volume
   if volume>.01:report['interferences_carbone_equipements'].append([n,obj.Name,round(volume,4)])
assert not report['interferences_carbone_equipements'],report['interferences_carbone_equipements']
report['interferences_fixations']=[]
for i,obj in enumerate(hardware):
 for other in hardware[i+1:]+equipment:
  if obj.Shape.BoundBox.intersect(other.Shape.BoundBox):
   volume=obj.Shape.common(other.Shape).Volume
   if volume>.01:report['interferences_fixations'].append([obj.Name,other.Name,round(volume,4)])
assert not report['interferences_fixations'],report['interferences_fixations']
report['interferences_colliers_ESC']=[]
for tie in [o for o in equipment if o.Name.startswith('Collier_ESC')]:
 for obj in equipment:
  if obj is tie:continue
  if tie.Shape.BoundBox.intersect(obj.Shape.BoundBox):
   volume=tie.Shape.common(obj.Shape).Volume
   if volume>.01:report['interferences_colliers_ESC'].append([tie.Name,obj.Name,round(volume,4)])
assert not report['interferences_colliers_ESC'],report['interferences_colliers_ESC']
cc=mp+mr.multVec(MOTOR_CENTER);centers=[(sx*cc.x,sy*cc.y) for sx in [-1,1] for sy in [-1,1]]
report['ecart_disques_helices_mm']=round(min(math.dist(a,b) for i,a in enumerate(centers) for b in centers[i+1:])-228.6,3)
report['interferences_disques_electronique']=[]
for i,(x,y) in enumerate(centers):
 sweep=Part.makeCylinder(114.3,26,V(x,y,30))
 for obj in equipment:
  if obj in elec.Group:
   volume=sweep.common(obj.Shape).Volume
   if volume>.01:report['interferences_disques_electronique'].append([i,obj.Name,round(volume,4)])
assert report['ecart_disques_helices_mm']>0 and not report['interferences_disques_electronique']
report['bras_pleins']=True;report['corniere_quantite']=0
(OUT/'.build/contours.json').write_text(json.dumps(contours,indent=2),encoding='utf-8');(OUT/'.build/verification.json').write_text(json.dumps(report,indent=2,ensure_ascii=False),encoding='utf-8')
# Separate planar layout at true scale (not a production nesting).
layout=D.addObject('App::Part','Vue_decoupe');layout.Label='03 / Pièces à plat, une de chaque / hors assemblage'
for key,xy in zip(forms,[(0,0),(180,90),(180,20),(160,-70),(160,-130)]):
 o=D.addObject('App::Link','Aplat_'+key);layout.addObject(o);o.setLink(masters[key]);o.LinkPlacement=App.Placement(V(xy[0],xy[1],0),App.Rotation());o.Visibility=True
layout.Visibility=False
lib.Visibility=False
D.recompute();D.saveAs(str(OUT/'chassis.FCStd'))
# Export assembly from globally positioned solids, independent from link visibility.
E=App.newDocument('Export_Chassis_CNC');ex=[]
for name,s in shapes:
 o=E.addObject('PartDesign::Feature',name);o.Shape=s;ex.append(o)
for spacer in hardware+equipment:
 o=E.addObject('PartDesign::Feature',spacer.Name);o.Shape=spacer.Shape;ex.append(o)
Import.export(ex,str(OUT/'chassis.step'));App.closeDocument(E.Name);App.setActiveDocument(D.Name)
if App.GuiUp:
 import FreeCADGui as Gui
 from pivy import coin
 v=Gui.activeDocument().activeView();v.viewAxonometric();v.fitAll();v.getCameraNode().height.setValue(510);D.save()
