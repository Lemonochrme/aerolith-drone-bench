import FreeCAD as App,FreeCADGui as Gui,Part,MeshPart,Import,json,math
from pathlib import Path
O=Path(globals().get('__file__',r'C:\Users\robin\Documents\Codex\2026-10-16\d-veloppe-un-banc-de-calibration-7\outputs\V3_Pivot_lacet\Revoir_pivot_V3.FCMacro')).resolve().parent
SRC=O/'Sources'/'Banc_IMU_V2_base.FCStd'
D=App.openDocument(str(SRC));D.Label='Banc IMU V3 — pivot lacet métallique guidé'
V=App.Vector
base=D.Socle;yaw=D.Lacet
for cell in ['B4','B5','B6']:D.Parametres.set(cell,'0')
# Discard only the superseded base turntable components in the new document copy.
for ob in list(D.Objects):
 if ob.Name.startswith(('CP_01_Embase','CP_02_Plateau_tournant','Roulement_plateau_tournant','Traverse_sur_CP_M6x25')):D.removeObject(ob.Name)
# Reuse the whole V2 gimbal above a 130 mm taller interface.
yaw.Placement.Base=V(0,0,130)
yaw.Label='02 — Fourche tournante / rehaussée de 130 mm'
D.Parametres.set('B7','895');D.Parametres.set('A16','V3 : pivot guidé UCF204 + butée 51104')
fixed=D.addObject('App::Part','PivotFixe');base.addObject(fixed);fixed.Label='08 — Cartouche fixe / deux paliers métalliques'
rotor=D.addObject('App::Part','PivotTournant');yaw.addObject(rotor);rotor.Placement.Base=V(0,0,-130);rotor.Label='09 — Arbre, butée, moyeu et index tournants'
new=[];metal=(.72,.76,.8);dark=(.17,.21,.23);blue=(.1,.42,.65);wood=(.76,.58,.34);orange=(.97,.48,.14)
def add(name,sh,parent,color=metal,spec='',kind=''):
 ob=D.addObject('PartDesign::Feature',name);ob.Label=name.replace('_',' ');ob.Shape=sh;parent.addObject(ob);ob.ViewObject.ShapeColor=color;ob.ViewObject.LineColor=(.16,.18,.2);ob.ViewObject.DisplayMode='Flat Lines'
 ob.addProperty('App::PropertyString','Specification','Fabrication');ob.Specification=spec;ob.addProperty('App::PropertyString','Categorie','Fabrication');ob.Categorie=kind;new.append(ob);return ob

def located(shape,pos,rr=None):
 sh=shape.copy();sh.Placement=App.Placement(V(*pos),rr or App.Rotation());return sh

def ring(ro,ri,t,z):return Part.makeCylinder(ro,t,V(0,0,z)).cut(Part.makeCylinder(ri,t,V(0,0,z)))
def drill(shape,x,y,r,z,h):return shape.cut(Part.makeCylinder(r,h,V(x,y,z)))
def hexsolid(af,t,pos,axis=(0,0,1)):
 r=af/math.sqrt(3);p=[V(r*math.cos(i*math.pi/3),r*math.sin(i*math.pi/3),0) for i in range(6)];sh=Part.Face(Part.makePolygon(p+[p[0]])).extrude(V(0,0,t));return located(sh,pos,App.Rotation(V(0,0,1),V(*axis)))
def washer(name,ri,ro,t,z,x=0,y=0,parent=fixed):return add(name,Part.makeCylinder(ro,t,V(x,y,z)).cut(Part.makeCylinder(ri,t,V(x,y,z))),parent,metal,'Rondelle acier standard','Visserie')
def screw(name,d,l,pos,axis,parent=fixed,hexhead=True):
 sh=Part.makeCylinder(d/2,l)
 if hexhead:sh=sh.fuse(hexsolid(d*1.6,d*.65,(0,0,-d*.65)))
 else:sh=sh.fuse(Part.makeCone(d,d/2,d*.55,V(0,0,-d*.55)))
 return add(name,located(sh,pos,App.Rotation(V(0,0,1),V(*axis))),parent,dark,'Visserie nominale, filets non représentés','Visserie')
# Fixed panel: all mounting patterns are now defined, no purchased turntable hole pattern.
cp=Part.makeBox(600,400,18,V(-300,-200,45))
for x in [-100,100]:
 for y in [-150,150]:cp=drill(cp,x,y,3.3,44,20)
cp=drill(cp,0,0,27.5,44,20)
for a in [32,65]:
 for x in [-a,a]:
  for y in [-a,a]:cp=drill(cp,x,y,5.5,44,20)
for x in [210,270]:cp=drill(cp,x,0,4.25,44,20)
add('CP05_Embase_pivot_600x400x18',cp,base,wood,'Remplace CP01 V2 : Ø55 central, 4 Ø11 à ±65, 4 Ø6,6 vers socle et 2 Ø6,6 pour pied indexeur','Bois')
# Cage plates: lower on base; upper bearing faces down, increasing bearing span without extreme height.
for name,z in [('AL02_Platine_inferieure_160x160x6',63),('AL03_Platine_superieure_160x160x6',163)]:
 sh=Part.makeBox(160,160,6,V(-80,-80,z));sh=drill(sh,0,0,27.5,z-1,8)
 for a in [32,65]:
  for x in [-a,a]:
   for y in [-a,a]:sh=drill(sh,x,y,5.5,z-1,8)
 if z==163:
  for x in [-50,50]:
   for y in [-50,50]:sh=drill(sh,x,y,4.5,z-1,8)
 add(name,sh,fixed,metal,'Aluminium 6 mm : carré de fixation UCF204 64, carré entretoises 130 ; plan DXF','Plat aluminium')
# Four long metallic cage ties, with double nuts to set separation exactly.
for x in [-65,65]:
 for y in [-65,65]:
  add('Tige_M10x170',Part.makeCylinder(5,170,V(x,y,20)),fixed,dark,'Tige filetée M10, longueur 170 mm ; 4 tirants, réglage des plans par écrous','Standard')
  for z in [27,35,71,79,145,153,171,179]:
   sh=hexsolid(17,8,(x,y,z)).cut(Part.makeCylinder(5,8,V(x,y,z)))
   add('Ecrou_M10_cage',sh,fixed,metal,'Écrou M10 ; compléter les contre-écrous au réglage (voir notice)','Visserie')
# Nominal UCF204 envelopes, from SNR dimensional table; outer housing stationary.
def unit(pos,rr,name):
 flange=Part.makeBox(86,86,11,V(-43,-43,0)).cut(Part.makeCylinder(23.5,12,V(0,0,-.5)))
 housing=flange.fuse(ring(31.5,23.5,25.5,0))
 for x in [-32,32]:
  for y in [-32,32]:housing=drill(housing,x,y,6,-1,28)
 add(name+'_F204',located(housing,pos,rr),fixed,blue,'UCF204 acheté : bride 86, entraxe 64, trous Ø12, hauteur 33,3. Géométrie simplifiée selon SNR.','Standard')
 insert=ring(23.5,10,31,2.3)
 add(name+'_UC204',located(insert,pos,rr),fixed,dark,'Insert simplifié : Ø20 / largeur 31, montage sur arbre lisse ; deux vis de blocage intégrées à la référence achetée','Standard')
unit((0,0,69),App.Rotation(),'UCF204_bas')
unit((0,0,163),App.Rotation(V(1,0,0),180),'UCF204_haut')
for x in [-32,32]:
 for y in [-32,32]:
  screw('UCF_bas_M10x50',10,50,(x,y,80),(0,0,-1))
  screw('UCF_haut_M10x35',10,35,(x,y,169),(0,0,-1))
# Four metal spacers support the axial thrust bridge above the UCF mounting bolt heads.
poly=[V(x,y,181) for x,y in [(-54,-60),(54,-60),(60,-54),(60,54),(54,60),(-54,60),(-60,54),(-60,-54)]];cap=Part.Face(Part.makePolygon(poly+[poly[0]])).extrude(V(0,0,6));cap=drill(cap,0,0,10.5,180,8)
for x in [-50,50]:
 for y in [-50,50]:
  cap=drill(cap,x,y,4.5,180,8)
  add('Entretoise_acier_M8_L12',Part.makeCylinder(7,12,V(x,y,169)).cut(Part.makeCylinder(4.25,12,V(x,y,169))),fixed,metal,'Entretoise métallique traversante Ø8,5 / longueur 12','Standard')
  screw('Pont_butee_M8x40',8,40,(x,y,187),(0,0,-1))
add('AL04_Pont_butee_120x120x6',cap,fixed,metal,'Plaque d’appui stationnaire de la butée, Ø21 central ; 4 M8 sur carré 100 ; coins coupés 6 × 6 pour dégager les contre-écrous','Plat aluminium')
# Dedicated axial bearing; lower washer stationary, upper washer and shaft rotate.
add('Butée_51104_rondelle_fixe',ring(17.5,10.5,3,187),fixed,dark,'Butée 51104 20×35×10, enveloppe en trois parties ; lubrifier selon fabricant','Standard')
add('Butée_51104_cage',ring(17,10.5,4,190),rotor,metal,'Cage et billes simplifiées, pas de calcul de contact','Standard')
add('Butée_51104_rondelle_tournante',ring(17.5,10,3,194),rotor,dark,'Appui supérieur du moyeu SHF20 sur la rondelle d’arbre','Standard')
add('Axe_lacet_20x200',Part.makeCylinder(10,200,V(0,0,20)),rotor,metal,'Arbre acier lisse Ø20 × 200 mm, sans usinage d’extrémité','Standard')
add('Bague_retenue_DIN705_20x32x14',ring(16,10,14,56.3),rotor,dark,'Retenue de secours anti-soulèvement ; jeu axial nominal 1 mm sous bague intérieure du palier bas ; vis pointeau à serrer','Standard')
# Real vendor SHF20: bore along original Y, flange mount plane Y=0, depth 20.
shf=Part.read(str(O/'Sources'/'SHF20.step'))
rr=App.Rotation(V(1,0,0),-90) # Y -> -Z; flange at 217, boss end at 197
add('Moyeu_metallique_SHF20',located(shf,(0,0,217),rr),rotor,metal,'SHF20 Motedis réel : trous à ±23,75 ; profondeur 20 ; face de bossage Ø30 sur butée 51104','Standard')
# Main rotating load plate is aluminium, attached directly to the 3060 beam.
pl=Part.makeBox(160,240,6,V(-80,-120,217));pl=drill(pl,0,0,10.5,216,8)
for x in [-23.75,23.75]:
 pl=drill(pl,x,0,3.3,216,8);pl=pl.cut(Part.makeCone(3.3,6.3,3,V(x,0,220)))
for x in [-15,15]:
 for y in [-90,90]:pl=drill(pl,x,y,3.3,216,8)
for x in [-60,60]:
 for y in [-90,90]:pl=drill(pl,x,y,2.75,216,8)
add('AL05_Plateau_tournant_160x240x6',pl,rotor,metal,'Liaison mécanique directe SHF20 / traverse 3060 ; M6 fraisées sur le moyeu ; M6 vers rainures du profilé','Plat aluminium')
for x in [-23.75,23.75]:screw('SHF20_M6x30_fraisee',6,26.7,(x,0,219.7),(0,0,-1),rotor,False)
for x in [-15,15]:
 for y in [-90,90]:screw('Traverse_M6x16',6,16,(x,y,217),(0,0,1),rotor)
# Index plate is an accessory, separate from the main vertical load path.
disc=ring(200,40,18,199)
for x in [-15,15]:
 for y in [-90,90]:disc=drill(disc,x,y,7,198,20)
for i in range(24):
 a=2*math.pi*i/24;disc=drill(disc,180*math.cos(a),180*math.sin(a),3.25,198,20)
for x in [-60,60]:
 for y in [-90,90]:
  disc=drill(disc,x,y,2.75,198,20)
  screw('Disque_index_M5x35',5,35,(x,y,223),(0,0,-1),rotor)
add('CP06_Disque_index_400x18',disc,rotor,wood,'CP 18 : Ø400, ouverture Ø80, 24 trous Ø6,5 sur Ø360 ; goupille amovible M6','Bois')
# Fixed index post and two ordinary 3030 brackets on the plywood base.
profile=Part.read(str(O/'Sources'/'3030.step'))
f=max([f for f in profile.Faces if f.BoundBox.ZLength<.0001 and abs(f.CenterOfMass.z)<.001],key=lambda f:f.Area).copy();b=profile.BoundBox;f.translate(V(-(b.XMin+b.XMax)/2,-(b.YMin+b.YMax)/2,0));post=f.extrude(V(0,0,120));post.translate(V(240,0,63))
add('Montant_index_3030_L120',post,fixed,metal,'Profilé 3030 B8, coupe 120 mm ; fixation sur panneau par deux équerres métalliques','Profilé')
br=Part.read(str(O/'Sources'/'bracket.step'))
for sx,rr in [(225,App.Rotation(V(1,0,0),90)),(255,App.Rotation(V(0,0,1),180).multiply(App.Rotation(V(1,0,0),90)))]:
 add('Equerre_index_3030',located(br,(sx,0,63),rr),fixed,metal,'S8BBR30 : vis de rainure M6x12, vis traversante panneau M6x35','Standard')
for x in [210,270]:screw('Pied_index_M6x35',6,35,(x,0,66),(0,0,-1))
# Printable socket/arm: not a bearing support; the weight path remains metallic.
arm=Part.makeBox(50,50,48,V(215,-25,143)).cut(Part.makeBox(30.4,30.4,41,V(224.8,-15.2,142)))
arm=arm.fuse(Part.makeBox(85,40,8,V(155,-20,183)))
arm=arm.cut(Part.makeCylinder(3.3,10,V(180,0,182)))
arm=arm.cut(Part.makeCylinder(3.3,12,V(254,0,163),V(1,0,0)))
for sy in [-1,1]:arm=arm.cut(Part.makeCylinder(3.3,12,V(240,sy*14,163),V(0,sy,0)))
arm=arm.cut(hexsolid(10.3,5.5,(180,0,183))).removeSplitter();add('Bras_index_lacet_imprime',arm,fixed,orange,'PETG, blocage sur trois rainures par M6x20 ; pas de charge verticale du banc dans cette pièce','Impression')
for p,a in [((265,0,163),(-1,0,0)),((240,25,163),(0,-1,0)),((240,-25,163),(0,1,0))]:screw('Capot_index_M6x20',6,20,p,a)
screw('Vis_index_lacet_M6x35_retiree',6,35,(180,0,160),(0,0,1))
# Print oriented on a side: use supports for the roof and arm; see guide.
pr=arm.copy();pr.translate(V(-155,25,-143));mesh=MeshPart.meshFromShape(Shape=pr,LinearDeflection=.12,AngularDeflection=.15,Relative=False);mesh.write(str(O/'STL'/'10_Bras_index_lacet_x1.stl'))
# Check and export all actually visible physical objects, excluding masked libraries and target volumes.
D.recompute()
visible=[]
for ob in D.Objects:
 if hasattr(ob,'Categorie') and hasattr(ob,'Shape') and ob.ViewObject.Visibility:
  parents=ob.InListRecursive
  if D.PiecesImprimees in parents or ob.Categorie=='Contrôle':continue
  visible.append(ob)
invalid=[o.Name for o in visible if not o.Shape.isValid() or len(o.Shape.Solids)==0]
report={'objets_visibles':len(visible),'solides':sum(len(o.Shape.Solids) for o in visible),'invalides':invalid,'rehausse_mm':130,'hauteur_axes_mm':895,'guidage_ecartement_centres_mm':64,'impression_index':{'dimensions_mm':[pr.BoundBox.XLength,pr.BoundBox.YLength,pr.BoundBox.ZLength],'solide':arm.isValid(),'maillage_ferme':mesh.isSolid()},'sources':{'UCF204':'https://eshop.ntn-snr.com/pt/product/UCF204-SNR/UCF204','51104':'https://www.nsk.com/jp-ja/engineering/51104-tb-sd.html','SHF20':'https://www.motedis.fr/fr/Supports-darbre-SHF20'}}
(O/'verification_V3.json').write_text(json.dumps(report,indent=2,ensure_ascii=False),encoding='utf-8')
D.saveAs(str(O/'Banc_IMU_V3_Pivot_lacet.FCStd'))
ex=App.newDocument('Export_V3');objs=[]
for ob in visible:
 q=ex.addObject('PartDesign::Feature',ob.Name);q.Shape=ob.Shape.copy();q.Placement=ob.getGlobalPlacement();q.ViewObject.ShapeColor=ob.ViewObject.ShapeColor;objs.append(q)
ex.recompute();Import.export(objs,str(O/'Banc_IMU_V3_Pivot_lacet.step'));App.closeDocument(ex.Name);App.setActiveDocument(D.Name)
v=Gui.activeDocument().activeView();v.viewAxonometric();v.fitAll();v.getCameraNode().height.setValue(1850);v.saveImage(str(O/'Banc_V3_vue_ensemble.png'),1800,1400,'White')
print(report)
