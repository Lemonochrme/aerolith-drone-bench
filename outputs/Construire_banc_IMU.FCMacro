import FreeCAD as App, FreeCADGui as Gui, Part, math, json, os, traceback
from pathlib import Path
OUT=Path(r'C:\Users\robin\Documents\Codex\2026-10-16\d-veloppe-un-banc-de-calibration-7\outputs')
V=App.Vector
D=App.newDocument('Banc_IMU_500')
S=D.addObject('Spreadsheet::Sheet','Parametres'); S.Label='00 — Paramètres / angles en degrés'
rows=[('Diagonale drone cible',500,'DroneDiagonal'),('Hauteur axes',650,'AxisHeight'),('Rayon extérieur tangage',365,'PitchRadius'),('Largeur anneaux',24,'RingWidth'),('Épaisseur anneaux',16,'RingThickness'),('Rayon extérieur roulis',310,'RollRadius'),('Demi entraxe montants',425,'PostOffset'),('Largeur socle',1000,'BaseSize'),('Lacet (°)',0,'Yaw'),('Tangage (°)',0,'Pitch'),('Roulis (°)',0,'Roll'),('Diamètre axes',20,'ShaftDiameter'),('Hauteur enveloppe drone',160,'DroneHeight')]
S.set('A1','PARAMÈTRE');S.set('B1','VALEUR mm / deg');S.setStyle('A1:B1','bold','add'); S.setBackground('A1:B1',(0.1,0.22,0.32)); S.setForeground('A1:B1',(1.,1.,1.))
for i,(label,value,alias) in enumerate(rows,2): S.set('A'+str(i),label);S.set('B'+str(i),str(value));S.setAlias('B'+str(i),alias)
S.setColumnWidth('A',270);S.setColumnWidth('B',150)
S.set('A17','V1 AVANT-PROJET — sans hélices, manuel'); S.set('A18','Angles : lacet Z → tangage Y → roulis X');S.set('A19','Singularité de cardan à tangage ±90°');S.set('A20','Dimensions = référence ; changements géométriques à revalider');S.set('A21','Seuls les trois angles sont pilotés sur tout l’assemblage')
base=D.addObject('App::Part','Socle');base.Label='01 — Socle fixe 1000 × 1000'
yaw=D.addObject('App::Part','Lacet');yaw.Label='02 — Lacet Z / fourche tournante'
yaw.Placement.Rotation=App.Rotation(V(0,0,1),0);yaw.setExpression('Placement.Rotation.Angle','Parametres.Yaw * 1 deg')
pitch=D.addObject('App::Part','Tangage');yaw.addObject(pitch);pitch.Label='03 — Tangage Y / anneau Ø730';pitch.Placement=App.Placement(V(0,0,650),App.Rotation(V(0,1,0),0));pitch.setExpression('Placement.Base.z','Parametres.AxisHeight');pitch.setExpression('Placement.Rotation.Angle','Parametres.Pitch * 1 deg')
roll=D.addObject('App::Part','Roulis');pitch.addObject(roll);roll.Label='04 — Roulis X / anneau Ø620';roll.Placement=App.Placement(V(),App.Rotation(V(1,0,0),0));roll.setExpression('Placement.Rotation.Angle','Parametres.Roll * 1 deg')
ref=D.addObject('App::Part','DroneReference');roll.addObject(ref);ref.Label='05 — Référence LithFrame / assemblage indicatif'
metal=(0.68,0.73,0.78); blue=(0.12,0.40,0.62); orange=(0.96,0.48,0.12); dark=(0.15,0.18,0.22); carbon=(0.22,0.24,0.27); green=(0.15,0.67,0.55)
solids=[]; bom=[]
def style(o,c):
 o.ViewObject.ShapeColor=c;o.ViewObject.LineColor=(0.12,0.14,0.17);o.ViewObject.DisplayMode='Flat Lines';return o
def item(name,shape,parent,color,desc=''):
 o=D.addObject('PartDesign::Feature',name);o.Label=name.replace('_',' ');o.Shape=shape;parent.addObject(o);style(o,color)
 if desc:o.addProperty('App::PropertyString','Specification','Documentation');o.Specification=desc
 solids.append(o);return o
def box(name,l,w,h,x,y,z,parent=base,color=metal):
 o=D.addObject('Part::Box',name);o.Label=name.replace('_',' ');o.Length=l;o.Width=w;o.Height=h;o.Placement.Base=V(x,y,z);parent.addObject(o);style(o,color);solids.append(o);return o
def cylinder(name,r,h,pos,axis=V(0,0,1),parent=base,color=metal):
 o=D.addObject('Part::Cylinder',name);o.Label=name.replace('_',' ');o.Radius=r;o.Height=h;o.Placement=App.Placement(V(*pos),App.Rotation(V(0,0,1),axis));parent.addObject(o);style(o,color);solids.append(o);return o
def ring(name,ro,ri,t,pos,axis,parent,color,expr=None):
 a=cylinder(name+'_brut',ro,t,pos,axis,parent,color);b=cylinder(name+'_vide',ri,t,pos,axis,parent,color)
 o=D.addObject('Part::Cut',name);o.Base=a;o.Tool=b;parent.addObject(o);style(o,color);a.Visibility=False;b.Visibility=False;solids.remove(a);solids.remove(b);solids.append(o)
 if expr:
  a.setExpression('Radius',expr);b.setExpression('Radius',expr+' - Parametres.RingWidth');a.setExpression('Height','Parametres.RingThickness');b.setExpression('Height','Parametres.RingThickness')
 return o
# Frame of closed aluminium square tubes, 40 x 40 x 3.
def tube(name,l,w,h,x,y,z,parent=base,color=metal):
 axis=max(range(3),key=lambda k:[l,w,h][k]); dims=[l,w,h];inner=[l,w,h];p=[x,y,z]
 for k in range(3):
  if k!=axis:inner[k]-=6;p[k]+=3
 p[axis]-=1;inner[axis]+=2
 return item(name,Part.makeBox(*dims,V(x,y,z)).cut(Part.makeBox(*inner,V(*p))),parent,color,'Tube aluminium 40 × 40 × 3 mm — coupes à confirmer')
for y in (-500,460):tube('Longeron_'+str(y),1000,40,40,-500,y,30)
for x in (-500,460):tube('Traverse_'+str(x),40,920,40,x,-460,30)
for x in (-90,50):tube('Support_plateau_'+str(x),40,920,40,x,-460,30)
for x in (-480,480):
 for y in (-480,480):
  cylinder('Patin',30,15,(x,y,0),color=dark);cylinder('Vis_pied_M12',6,25,(x,y,15))
box('Plaque_support_lacet',250,250,10,-125,-125,70)
ring('Roulement_lacet_enveloppe',90,55,25,(0,0,80),V(0,0,1),base,dark)
cylinder('Moyeu_lacet',50,65,(0,0,100),parent=yaw,color=blue)
box('Plateau_lacet',220,220,15,-110,-110,165,yaw,blue)
# U frame; posts clear the swept pitch radius.
beam=box('Traverse_fourche',60,900,60,-30,-450,180,yaw,blue)
for sign in (-1,1):
 post=box('Montant_'+str(sign),60,40,450,-30,sign*425-20,240,yaw,blue);post.setExpression('Height','Parametres.AxisHeight - 200')
 # plate housing with bearing bore parallel to Y
 p=V(-35,sign*425-12,615);housing=Part.makeBox(70,24,70,p).cut(Part.makeCylinder(21,26,V(0,sign*425-13,650),V(0,1,0)))
 item('Palier_tangage_'+str(sign),housing,yaw,metal,'Logement conceptuel 2 × 6004 par axe, Ø20/42/12 ; ajustements à définir')
 ring('Roulement_tangage_'+str(sign),21,10,12,(0,sign*425-6,650),V(0,1,0),yaw,dark)
 # long trunnion bridges from ring OD to housing, signed orientation
 cylinder('Tourillon_tangage_'+str(sign),10,130,(0,sign*355,0),V(0,sign,0),pitch,metal)
 # broad lug around attachment at ring
 lug=Part.makeBox(50,28,34,V(-25,sign*353-14,-17))
 item('Chape_tangage_'+str(sign),lug,pitch,blue,'Fixation mécanique de la chape par 4 vis M5 à détailler')
outer=ring('Anneau_tangage',365,341,16,(0,0,-8),V(0,0,1),pitch,blue,'Parametres.PitchRadius')
inner=ring('Anneau_roulis',310,286,16,(0,0,-8),V(0,0,1),roll,orange,'Parametres.RollRadius')
for sign in (-1,1):
 # Housing at X +/- 353, on pitch ring. Bore parallel to X.
 h=Part.makeBox(24,60,60,V(sign*353-12,-30,-30)).cut(Part.makeCylinder(21,26,V(sign*353-13,0,0),V(1,0,0)))
 item('Palier_roulis_'+str(sign),h,pitch,metal)
 ring('Roulement_roulis_'+str(sign),21,10,12,(sign*353-6,0,0),V(1,0,0),pitch,dark)
 cylinder('Tourillon_roulis_'+str(sign),10,110,(sign*300,0,0),V(sign,0,0),roll,metal)
 item('Chape_roulis_'+str(sign),Part.makeBox(28,44,28,V(sign*298-14,-22,-14)),roll,orange)
# Indexing concept: 24 positions / 15 degrees. Pin retracts before rotation.
def indexdisc(name,pos,axis,parent):
 shape=Part.makeCylinder(62,6,V(),V(0,0,1)).cut(Part.makeCylinder(10,6,V(),V(0,0,1)))
 for i in range(24):
  a=2*math.pi*i/24;shape=shape.cut(Part.makeCylinder(2.5,8,V(48*math.cos(a),48*math.sin(a),-1)))
 shape.Placement=App.Placement(V(*pos),App.Rotation(V(0,0,1),axis))
 return item(name,shape,parent,metal,'Disque Ø124 × 6 ; 24 trous Ø5 sur Ø96 ; indexage 15° ; moyeu fendu à détailler')
indexdisc('Index_tangage_15deg',(0,462,0),V(0,1,0),pitch)
box('Support_index_tangage',25,25,65,35,413,625,yaw,blue)
box('Bras_index_tangage',25,43,12,35,438,644,yaw,blue)
cylinder('Pion_tangage_retractable',2.4,25,(48,452,650),V(0,1,0),yaw,dark)
cylinder('Poignee_tangage',19,12,(0,480,0),V(0,1,0),pitch,dark)
indexdisc('Index_roulis_15deg',(385,0,0),V(1,0,0),roll)
box('Support_index_roulis',20,25,40,345,-12,25,pitch,blue)
box('Bras_index_roulis',40,20,12,365,-10,42,pitch,blue)
cylinder('Pion_roulis_retractable',2.4,25,(375,0,48),V(1,0,0),pitch,dark)
cylinder('Poignee_roulis',19,12,(405,0,0),V(1,0,0),roll,dark)
# Yaw detent disc larger than the bearing, on rotating shaft.
shape=Part.makeCylinder(145,6,V(0,0,150)).cut(Part.makeCylinder(50,6,V(0,0,150)))
for i in range(24):
 a=2*math.pi*i/24;shape=shape.cut(Part.makeCylinder(2.5,8,V(130*math.cos(a),130*math.sin(a),149)))
item('Index_lacet_15deg',shape,yaw,metal,'Disque Ø290 × 6, 24 trous Ø5 sur Ø260 ; fixation moyeu à détailler')
box('Support_index_lacet',30,30,65,115,-15,80,base,metal)
cylinder('Pion_lacet_retractable',2.4,25,(130,0,140),V(0,0,1),base,dark)

# Drop frame, all within inner free sphere; 4 columns contact underside of inner ring.
for y in (-65,65):
 box('Rail_porte_drone',592,20,12,-296,y-10,-78,roll,dark)
 for sign in (-1,1):box('Entretoise_cadre',18,20,58,sign*289-9,y-10,-66,roll,orange)
plate=Part.makeBox(160,300,8,V(-80,-150,-86))
# Square 50 / 70 pattern matching provided central plate; support slots permit adjustment.
for x in (-25,25):
 for y in (-25,25):plate=plate.cut(Part.makeCylinder(2.25,10,V(x,y,-87)))
for x in (-35,35):
 for y in (-35,35):plate=plate.cut(Part.makeCylinder(2.25,10,V(x,y,-87)))
for x in (-60,60):
 for y in (-100,100):
  slot=Part.makeBox(6.5,24,10,V(x-3.25,y-12,-87)).fuse(Part.makeCylinder(3.25,10,V(x,y-12,-87))).fuse(Part.makeCylinder(3.25,10,V(x,y+12,-87)))
  plate=plate.cut(slot)
item('Platine_adaptation_160x300',plate,roll,metal,'Aluminium 8 mm ; perçages Ø4,5 sur carrés 50 et 70 mm ; 4 lumières 6,5 × 30,5')
for x in (-25,25):
 for y in (-25,25):
  cylinder('Entretoise_M4',4,43,(x,y,-78),parent=roll,color=green)
  cylinder('Vis_M4_reference',2,58,(x,y,-90),parent=roll,color=dark)
# DXF exact outlines. The base drawing has tiny endpoint gaps; close using 0.01 mm sorting tolerance.
source=json.loads((OUT/'contours_source.json').read_text(encoding='utf-8'))
faces={}
for name,entities in source.items():
 edges=[]
 for e in entities:
  if e[0]=='LINE':edges.append(Part.makeLine(V(*e[1]),V(*e[2])))
  elif e[0]=='CIRCLE':edges.append(Part.makeCircle(e[2],V(*e[1])))
  elif e[0]=='ARC':edges.append(Part.makeCircle(e[2],V(*e[1]),V(0,0,1),e[3],e[4] if e[4]>e[3] else e[4]+360))
 for edge in edges:edge.fixTolerance(.001)
 faces[name]=Part.makeFace([Part.Wire(w) for w in Part.sortEdges(edges,.01)],'Part::FaceMakerBullseye')
basekey=next(k for k in faces if k.startswith('Base'))
o=item('LithFrame_base_DXF',faces[basekey].extrude(V(0,0,3)),ref,carbon,'Contours source DXF ; épaisseur 3 mm supposée ; orientation Y longitudinal');o.Placement.Base=V(0,0,-35)
# Source parts library: do not invent assembled arm locations from flat parts.
lib=D.addObject('App::Part','Bibliotheque_DXF');lib.Label='06 — Pièces DXF sources / masquées'
for name,f in faces.items():
 ob=item('Source_'+name.replace(' ','_'),f.extrude(V(0,0,3)),lib,carbon,'Géométrie DXF source, épaisseur supposée 3 mm');ob.Visibility=False
lib.Visibility=False
# Representative target volume, hidden by default.
env=D.addObject('Part::Cylinder','Enveloppe_drone_500');ref.addObject(env);env.Label='Enveloppe cible Ø500 × 160 / afficher pour contrôler';env.Radius=250;env.Height=160;env.Placement.Base=V(0,0,-80);style(env,green);env.ViewObject.Transparency=85;env.Visibility=False
# Axes visual markers (hidden in STEP and save view).
axes=D.addObject('App::Part','Reperes');axes.Label='07 — Repères axes / masqués'
for name,axis,c in [('X_roulis',V(1,0,0),(1.,0.2,0.2)),('Y_tangage',V(0,1,0),(0.2,0.8,0.3)),('Z_lacet',V(0,0,1),(0.2,0.4,1.))]:
 ob=cylinder(name,2,500,(0,0,650),axis,axes,c);ob.Visibility=False
axes.Visibility=False
D.recompute()
# Check native BRep bodies and exported mechanical objects.
visible=[o for o in solids if o.Visibility and o not in lib.Group and o not in axes.Group]
checks=[]
for o in visible:
 checks.append({'piece':o.Name,'valid':o.Shape.isValid(),'solids':len(o.Shape.Solids),'volume_mm3':o.Shape.Volume})
report={'document':D.Name,'parts':len(checks),'invalid':[r for r in checks if not r['valid'] or r['solids']==0], 'checks':checks, 'clearances_mm':{'enveloppe_drone_vers_anneau_roulis':286-math.sqrt(250**2+80**2),'sweep_anneau_roulis_vers_tangage':341-math.sqrt(310**2+8**2),'anneau_tangage_vers_fourche':405-math.sqrt(365**2+8**2),'anneau_tangage_vers_traverse':650-math.sqrt(365**2+8**2)-240},'source_dxf':{'units':'mm','base_dimensions':[126,270],'short_arm_length':160,'long_arm_length':190,'source_thickness_assumption':3,'endpoint_join_tolerance_mm':.01},'limitations':['Avant-projet manuel, pas de validation structurelle','Chapes, freins, indexeurs esquissés : tolérances et fixations à détailler','Pas de simulation dynamique ni calibration métrologique','Assemblage complet du drone non déductible des pièces à plat']}
(OUT/'verification_geometrie.json').write_text(json.dumps(report,indent=2,ensure_ascii=False),encoding='utf-8')
Gui.activeDocument().activeView().viewAxonometric();Gui.activeDocument().activeView().fitAll()
Gui.activeDocument().activeView().setAnimationEnabled(False) if hasattr(Gui.activeDocument().activeView(),'setAnimationEnabled') else None
D.recompute();D.saveAs(str(OUT/'Banc_IMU_F380_500.FCStd'))
# Part export retains individual solids and global placements.
import Import
exportdoc=App.newDocument('Export_STEP')
exportitems=[]
for obj in visible:
 tmp=exportdoc.addObject('PartDesign::Feature',obj.Name)
 tmp.Label=obj.Label
 tmp.Shape=obj.Shape.copy()
 tmp.Placement=obj.getGlobalPlacement()
 tmp.ViewObject.ShapeColor=obj.ViewObject.ShapeColor
 exportitems.append(tmp)
exportdoc.recompute()
Import.export(exportitems,str(OUT/'Banc_IMU_F380_500.step'))
App.closeDocument(exportdoc.Name)
App.setActiveDocument(D.Name)
Gui.activeDocument().activeView().saveImage(str(OUT/'Banc_IMU_vue_ensemble.png'),1800,1400,'White')
# Exploit live additive MCP bridge on localhost only.
try:
 import sys
 p=os.path.join(App.getUserAppDataDir(),'Mod','FreeCADMCP')
 if p not in sys.path:sys.path.insert(0,p)
 from rpc_server import rpc_server
 msg=rpc_server.start_rpc_server()
 (OUT/'etat_mcp.txt').write_text(msg+'\nAddon: '+p,encoding='utf-8')
except Exception:
 (OUT/'etat_mcp.txt').write_text(traceback.format_exc(),encoding='utf-8')
(OUT/'construction_terminee.txt').write_text('OK',encoding='utf-8')
